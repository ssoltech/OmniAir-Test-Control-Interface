--OSS.PDU TCI-16093.TSI16093Event>--
TCI-indication
DEFINITIONS AUTOMATIC TAGS ::=
BEGIN

IMPORTS
IPv6Address,
ChannelNumber80211,
TXpower80211,
DataRate80211,
MACaddress FROM IEEE-1609-3-WEE {iso(1) identified-organization(3) ieee(111) standards-association-numbered-series-standards(2) wave-stds(1609) dot3(3) wee(1) version0(0)}

ResultCode,
PduType,
PduData,
RCPI,
TimeSlot,
RepeatRate,
UserPriority,
Opaque,
HashedId8,
Exception,
RadioInterface,
Psid,
Time64,
--IpAddress,
MsgID FROM TCI-CommonTypes
;

/*
   Indication Messages
*/
Indication ::= SEQUENCE{
    radio                   RadioInterface ( WITH COMPONENTS { ..., antenna ABSENT }),
    event                   Event,
    eventParams             EventParams OPTIONAL,
    pdu                     Pdu OPTIONAL,
    exception               Exception OPTIONAL,
    ...
}

Event ::= ENUMERATED {
    eRadioPktRx                         (1),    -- used for 802.11 frames or PC5 Mac frames
    e16093PktRx                         (2),    -- inbound 1603 frame received (before PSID filtering)
    eWsmPktRx                           (3),    -- WSM received (after PSID match _AND_ filter based on pduFilter (if present))
    eIpv6PktRx                          (4),    -- inbound IPv6 frame received
    eIcmp6PktRx                         (5),    -- inbound ICMP frame received
    eIpv6ConfigChanged                  (6),    -- IPv6 address configuration changed
    eDot3ChannelAssigned                (7),    -- Channel assigned as per WME-Notification.indication
    eDot3RequestMatchedAvailAppService  (8),    -- request matched with available application-service as per WME-Notification.indication
    eDot2VerificationCompleteWithResult (9),    -- message signature verification is complete
	  eDot2Dot1                           (10),   -- dot2dot1 indication received 
    exception                           (15)    -- exception reported from IUT
}

EventParams ::= CHOICE{
    service         [0]     ServiceParameters,
    wsm             [1]     WsmParameters,
    ip              [2]     IpParameters,
    radioframe      [3]     RadioParameters,
    security        [4]     SecResultParams,
    ...,
    dot2dot1        [5]     Dot2Dot1Params
}

Pdu ::= SEQUENCE {
    pduType     PduType,
    pduData     PduData,
    ...
}

ServiceParameters ::= SEQUENCE{ -- used in EventParams
    psid                    SEQUENCE OF Psid,
    ...
}

WsmParameters ::= SEQUENCE{ -- used in EventParams for 802.11 or LTE-V2X (with irrelevant parameters omitted)
    radio                   RadioInterface ( WITH COMPONENTS { ..., antenna ABSENT }),
    psid                    Psid,
    wsmpVersion             INTEGER(0..15),
    channelIdentifier       ChannelNumber80211 OPTIONAL,
    dataRate                DataRate80211 OPTIONAL,
    receivePowerLevel       TXpower80211 OPTIONAL,
    sourceMACAddr           MACaddress OPTIONAL,
    ...,
    -- ADD any other parameters including LTE-V2X
    rssi                    RCPI OPTIONAL
}

IpParameters ::= SEQUENCE{ -- used in EventParams
    interfaceName           UTF8String(SIZE(1..255)),
    sourceIPaddress         IPv6Address,
    protocol                ENUMERATED { tcp, udp, icmpv6 }, -- Upper Layer protocol used for the IPv6 PDU provided in the same TCI indication.
    ...
}

RadioParameters ::= SEQUENCE{ -- used in EventParams
    radio                   RadioInterface ( WITH COMPONENTS { ..., antenna ABSENT }),
    rcpi                    RCPI,
    ...
}

SecResultParams ::= SEQUENCE { -- used in EventParams
    securityResultCode      ResultCode,
                            -- All errors are lumped into single result code
                            -- Specific cause of error to be described in the SecResultParams.description    
    description             OCTET STRING OPTIONAL,
    ...
}

Dot2Dot1Params ::= SEQUENCE {
    state                   Dot2Dot1State,
    ...
}

Dot2Dot1State ::= ENUMERATED {
    eInitialised            (1),
    eEnrolled               (2),
    eAuthReqResp            (3),
    eAuthDownResp           (4),
    eProvisioned            (5),
    eCcfDownResp            (6),
    eCrlDownResp            (7),
    eMbrTriggeredResp       (8),
    exception               (15) --exception added with large value to allow for future expansion
}

-- SecurityResultCode ::= ENUMERATED {     
--    success (1),
--    inconsistentInputParameters (2),
--    spduParsingInvalidInput (3),
--    spduParsingUnsupportedCriticalInformationField (4),
--    spduParsingCertificateNotFound (5),
--    spduParsingGenerationTimeNotAvailable (6),
--    spduParsingGenerationLocationNotAvailable (7),
--    spduCertificateChainNotEnoughInformationToConstructChain (8),
--    spduCertificateChainChainEndedAtUntrustedRoot (9),
--    spduCertificateChainChainWasTooLongForImplementation (10),
--    spduCertificateChainCertificateRevoked (11),
--    spduCertificateChainOverdueCRL (12),
--    spduCertificateChainInconsistentExpiryTimes (13),
--    spduCertificateChainInconsistentStartTimes (14),
--    spduCertificateChainInconsistentChainPermissions (15),
--    spduCryptoVerificationFailure (16),
--    spduConsistencyFutureCertificateAtGenerationTime (17),
--    spduConsistencyExpiredCertificateAtGenerationTime (18),
--    spduConsistencyExpiryDateTooEarly (19),
--    spduConsistencyExpiryDateTooLate (20),
--    spduConsistencyGenerationLocationOutsideValidityRegion (21),
--    spduConsistencyNoGenerationLocation (22),
--    spduConsistencyUnauthorizedPSID (23),
--    spduInternalConsistencyExpiryTimeBeforeGenerationTime (24),
--    spduInternalConsistencyextDataHashDoesntMatch (25),
--    spduInternalConsistencynoExtDataHashProvided (26),
--    spduInternalConsistencynoExtDataHashPresent (27),
--    spduLocalConsistencyPSIDsDontMatch (28),
--    spduLocalConsistencyChainWasTooLongForSDEE (29),
--    spduRelevanceGenerationTimeTooFarInPast (30),
--    spduRelevanceGenerationTimeTooFarInFuture (31),
--    spduRelevanceExpiryTimeInPast (32),
--    spduRelevanceGenerationLocationTooDistant (33),
--    spduRelevanceReplayedSpdu (34),
--    spduRelevanceCertificateExpired (35),
--    spduCertificateChainInconsistentValidityRegion (36)
-- }

END
